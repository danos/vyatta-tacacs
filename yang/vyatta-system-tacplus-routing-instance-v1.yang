module vyatta-system-tacplus-routing-instance-v1 {
	namespace "urn:vyatta.com:mgmt:vyatta-system-tacplus-routing-instance:1";
	prefix vyatta-system-tacplus-routing-instance-v1;

	import vyatta-system-v1 {
		prefix system;
	}
	import vyatta-system-login-v1 {
		prefix system-login;
	}
	import vyatta-routing-v1 {
		prefix rt-instance;
	}
	import vyatta-routing-instance-interfaces-v1 {
		prefix rif;
	}
	import vyatta-system-tacplus-v1 {
		prefix system-tacplus;
	}

	organization "AT&T Inc.";
	contact
		"AT&T
		 Postal: 208 S. Akard Street
				 Dallas, TX 75202
		 Web: www.att.com";

	description
		"Copyright (c) 2017 AT&T Intellectual Property
		 All rights reserved.

		 Copyright (c) 2016-2017 by Brocade Communications Systems, Inc.
		 All rights reserved.

         Redistribution and use in source and binary forms, with or without
         modification, are permitted provided that the following conditions
         are met:

         1. Redistributions of source code must retain the above copyright
            notice, this list of conditions and the following disclaimer.
         2. Redistributions in binary form must reproduce the above
            copyright notice, this list of conditions and the following
            disclaimer in the documentation and/or other materials provided
            with the distribution.
         3. Neither the name of the copyright holder nor the names of its
            contributors may be used to endorse or promote products derived
            from this software without specific prior written permission.

         THIS SOFTWARE IS PROVIDED BY THE COPYRIGHT HOLDERS AND CONTRIBUTORS
         'AS IS' AND ANY EXPRESS OR IMPLIED WARRANTIES, INCLUDING, BUT NOT
         LIMITED TO, THE IMPLIED WARRANTIES OF MERCHANTABILITY AND FITNESS
         FOR A PARTICULAR PURPOSE ARE DISCLAIMED. IN NO EVENT SHALL THE
         COPYRIGHT HOLDER OR CONTRIBUTORS BE LIABLE FOR ANY DIRECT, INDIRECT,
         INCIDENTAL, SPECIAL, EXEMPLARY, OR CONSEQUENTIAL DAMAGES (INCLUDING,
         BUT NOT LIMITED TO, PROCUREMENT OF SUBSTITUTE GOODS OR SERVICES;
         LOSS OF USE, DATA, OR PROFITS; OR BUSINESS INTERRUPTION) HOWEVER
         CAUSED AND ON ANY THEORY OF LIABILITY, WHETHER IN CONTRACT, STRICT
         LIABILITY, OR TORT (INCLUDING NEGLIGENCE OR OTHERWISE) ARISING IN
         ANY WAY OUT OF THE USE OF THIS SOFTWARE, EVEN IF ADVISED OF THE
         POSSIBILITY OF SUCH DAMAGE.

         SPDX-License-Identifier: BSD-3-Clause

		 The YANG module for vyatta-system-tacplus-routing-instance-v1";

	revision 2017-12-07 {
		description "Add must constraint to source-interface leaf";
	}
    revision 2017-02-09 {
        description "Rework YANG nodeset != comparison";
    }
	revision 2016-02-19 {
		description "Add routing instance support for TACACS+";
	}

	augment /rt-instance:routing/rt-instance:routing-instance/rt-instance:system/rt-instance:login {
		uses system-tacplus:tacplus-system-login-grouping {
			refine tacplus-server {
				must "count(/system:system/system-login:login/system-tacplus:tacplus-server) = 0" {
					error-message "Cannot also configure TACACS+ in default routing-instance";
				}
				must "count(/rt-instance:routing/rt-instance:routing-instance[not(rt-instance:instance-name ="
				+ "current()/../../../rt-instance:instance-name)]/rt-instance:system/rt-instance:login/tacplus-server) = 0" {
					error-message "Cannot configure TACACS+ in more than one routing-instance simultaneously";
				}
			}

			refine tacplus-server/source-interface {
				must "current() = /rt-instance:routing/rt-instance:routing-instance" +
						"[rt-instance:instance-name = current()/../../../../rt-instance:instance-name]" +
						"/rif:interface/rif:name" {
					error-message "Interface must be configured in this routing instance";
				}
			}
		} 
	}
}
