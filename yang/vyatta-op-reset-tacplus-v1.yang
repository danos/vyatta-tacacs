module vyatta-op-reset-tacplus-v1 {
    namespace "urn:vyatta.com:mgmt:vyatta-op-reset-tacplus:1";
    prefix vyatta-op-reset-tacplus;

    import vyatta-opd-extensions-v1 {
        prefix opd;
    }
    import vyatta-op-reset-v1 {
        prefix op-reset;
    }
    import vyatta-op-reset-system-v1 {
        prefix op-reset-system;
    }
    import vyatta-op-reset-system-login-v1 {
        prefix op-reset-system-login;
    }

    organization "AT&T, Inc.";
    contact
        "AT&T
         Postal: 208 S. Akard Street
                 Dallas, TX 75202
         Web: www.att.com";

    description
        "Copyright (c) 2020, AT&T Intellectual Property.
         All rights reserved.

         Redistribution and use in source and binary forms, with or
         without modification, are permitted provided that the following
         conditions are met:

         1. Redistributions of source code must retain the above copyright
            notice, this list of conditions and the following disclaimer.
         2. Redistributions in binary form must reproduce the above
            copyright notice, this list of conditions and the following
            disclaimer in the documentation and/or other materials provided
            with the distribution.
         3. Neither the name of the copyright holder nor the names of its
            contributors may be used to endorse or promote products derived
            from this software without specific prior written permission.

         THIS SOFTWARE IS PROVIDED BY THE COPYRIGHT HOLDERS AND CONTRIBUTORS
         'AS IS' AND ANY EXPRESS OR IMPLIED WARRANTIES, INCLUDING, BUT NOT
         LIMITED TO, THE IMPLIED WARRANTIES OF MERCHANTABILITY AND FITNESS
         FOR A PARTICULAR PURPOSE ARE DISCLAIMED. IN NO EVENT SHALL THE
         COPYRIGHT HOLDER OR CONTRIBUTORS BE LIABLE FOR ANY DIRECT, INDIRECT,
         INCIDENTAL, SPECIAL, EXEMPLARY, OR CONSEQUENTIAL DAMAGES (INCLUDING,
         BUT NOT LIMITED TO, PROCUREMENT OF SUBSTITUTE GOODS OR SERVICES;
         LOSS OF USE, DATA, OR PROFITS; OR BUSINESS INTERRUPTION) HOWEVER
         CAUSED AND ON ANY THEORY OF LIABILITY, WHETHER IN CONTRACT, STRICT
         LIABILITY, OR TORT (INCLUDING NEGLIGENCE OR OTHERWISE) ARISING IN
         ANY WAY OUT OF THE USE OF THIS SOFTWARE, EVEN IF ADVISED OF THE
         POSSIBILITY OF SUCH DAMAGE.

         SPDX-License-Identifier: BSD-3-Clause

         This module implements reset operational CLI for TACACS+";

    revision 2020-08-12 {
        description "Initial revision";
    }

    feature reset-login-tacplus {
        description "Toggle the 'reset system login tacplus' operational command";
    }

    opd:augment /op-reset:reset/op-reset-system:system {
        opd:command tacplus {
            opd:help "Reset TACACS+ state";

            opd:command suppression-timers {
                opd:help "Reset TACACS+ hold-down/offline timers";
                opd:on-enter "vyatta-tacplus-op reset-suppression-timers";
            }
        }
    }

    opd:augment /op-reset:reset/op-reset-system:system/op-reset-system-login:login {
        if-feature reset-login-tacplus;
        opd:command tacplus {
            opd:help "Attempt to bring TACACS+ login services online";
            opd:privileged true;
            opd:on-enter "vyatta-tacplus-login-reset";
        }
    }
}
