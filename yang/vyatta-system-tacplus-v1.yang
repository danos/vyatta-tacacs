module vyatta-system-tacplus-v1 {
	namespace "urn:vyatta.com:mgmt:vyatta-system-tacplus:1";
	prefix vyatta-system-tacplus-v1;

	import vyatta-system-v1 {
		prefix system;
	}
	import vyatta-system-login-v1 {
		prefix system-login;
	}
	import vyatta-types-v1 {
		prefix types;
	}
	import configd-v1 {
		prefix configd;
	}
	import vyatta-interfaces-v1 {
		prefix if;
	}
	import vyatta-dscp-v1 {
		prefix dscp;
	}
 
	organization "AT&T Inc.";
	contact
		"AT&T
		 Postal: 208 S. Akard Street
				 Dallas, TX 75202
		 Web: www.att.com";

	description
		"Copyright (c) 2017-2020 AT&T Intellectual Property
		 All rights reserved.

		 Copyright (c) 2014-2016 by Brocade Communications Systems, Inc.
		 All rights reserved.

         Redistribution and use in source and binary forms, with or without
         modification, are permitted provided that the following conditions
         are met:

         1. Redistributions of source code must retain the above copyright
            notice, this list of conditions and the following disclaimer.
         2. Redistributions in binary form must reproduce the above
            copyright notice, this list of conditions and the following
            disclaimer in the documentation and/or other materials provided
            with the distribution.
         3. Neither the name of the copyright holder nor the names of its
            contributors may be used to endorse or promote products derived
            from this software without specific prior written permission.

         THIS SOFTWARE IS PROVIDED BY THE COPYRIGHT HOLDERS AND CONTRIBUTORS
         'AS IS' AND ANY EXPRESS OR IMPLIED WARRANTIES, INCLUDING, BUT NOT
         LIMITED TO, THE IMPLIED WARRANTIES OF MERCHANTABILITY AND FITNESS
         FOR A PARTICULAR PURPOSE ARE DISCLAIMED. IN NO EVENT SHALL THE
         COPYRIGHT HOLDER OR CONTRIBUTORS BE LIABLE FOR ANY DIRECT, INDIRECT,
         INCIDENTAL, SPECIAL, EXEMPLARY, OR CONSEQUENTIAL DAMAGES (INCLUDING,
         BUT NOT LIMITED TO, PROCUREMENT OF SUBSTITUTE GOODS OR SERVICES;
         LOSS OF USE, DATA, OR PROFITS; OR BUSINESS INTERRUPTION) HOWEVER
         CAUSED AND ON ANY THEORY OF LIABILITY, WHETHER IN CONTRACT, STRICT
         LIABILITY, OR TORT (INCLUDING NEGLIGENCE OR OTHERWISE) ARISING IN
         ANY WAY OUT OF THE USE OF THIS SOFTWARE, EVEN IF ADVISED OF THE
         POSSIBILITY OF SUCH DAMAGE.

         SPDX-License-Identifier: BSD-3-Clause

		 The YANG module for vyatta-system-tacplus-v1";

	revision 2020-10-13 {
		description "Set configd:priority 400 on the tacplus-options container";
	}

	revision 2019-05-06 {
		description "Add global DSCP value configuration";
	}

	revision 2019-05-02 {
		description "Add configurable service attribute for command authorization";
	}

	revision 2019-02-13 {
		description "Rework configd scripts under tacplus-options";
	}

	revision 2018-07-13 {
		description
			"Add hold-down-timer leaf.
			 Add command-authorization container.";
	}

	revision 2018-06-15 {
		description "Externalize hard limit of 100 servers.";
	}

	revision 2017-12-14 {
		description "Add source-interface leaf";
	}

	revision 2016-02-19 {
		description "Create grouping for tacplus.";
	}

	revision 2015-08-18 {
		description "Use canned type for IPv4/IPv6 address.";
	}

	revision 2015-08-14 {
		description "Initial revision of version 1.";
	}

	feature tacplus-server-source-interface {
		description
			"Enable source-interface configuration for a
			 TACACS+ server connection";
	}

	augment /system:system {
		container tacplus-options {
			presence "TACACS+ options have been configured";
			configd:end "/opt/vyatta/sbin/vyatta_system_update_aaa_tacplus";
			configd:priority "400";
			description 'TACACS+ parameters allow individual TACACS+ AAA functionality
					to be enabled.

					TACACS+ Authentication is enabled via the:
					"system login tacplus-server" configuration node.

					The "tacplus-options" node allows the optional command-accounting
					and command-authorization to be enabled.

					TACACS+ command-authorization is only applied to users authenticated
					via TACACS+.';
			configd:help "TACACS+ parameters";
			leaf command-accounting {
				description "Enables TACACS+ command accounting for all users.";
				type empty;
				configd:help "TACACS+ command accounting";
			}
			container command-authorization {
				description "Enables TACACS+ command authorization for TACACS+ authenticated users.";
				configd:help "TACACS+ command authorization";
				presence "TACACS+ command-authorization has been configured";
				container attributes {
					description "Configure attributes sent in requests";
					configd:help "Configure attributes sent in requests";
					leaf service {
						description "Set the 'service' attribute value";
						configd:help "Set the 'service' attribute value";
						default vyatta-exec;
						type enumeration {
							enum vyatta-exec {
								description "Use 'service=vyatta-exec'";
								configd:help "Use 'service=vyatta-exec'";
							}
							enum shell {
								description "Use 'service=shell'";
								configd:help "Use 'service=shell'";
							}
						}
					}
				}
			}
			container server {
				configd:end "vyatta-tacplusd-config";
				configd:help "Global TACACS+ server options";
				description "Global TACACS+ server options";
				leaf dscp {
					type dscp:dscp-name-or-value-with-cs0;
					configd:help "The IP DSCP value used for TACACS+ packets";
					description "The IP DSCP value used for TACACS+ packets";
					default cs6;
				}
			}
		}
	}
	grouping tacplus-system-login-grouping {
		list tacplus-server {
			configd:help "TACACS+ server address";
			max-elements 100;
			ordered-by "user";
			key "tagnode";
			leaf tagnode {
				type types:ip-address;
				configd:help "TACACS+ server address";
			}
			leaf source-address {
				type types:ip-address;
				configd:help "Source address to use for connecting to TACACS+ server";
			}
			uses if:source-interface-leaf {
				if-feature "tacplus-server-source-interface";
				refine source-interface {
					configd:help "Use source address from interface for connecting to the server";
					description
						"The interface used to obtain the source IP address for
						packets sent to the TACACS+ server.

						If the interface has multiple IP addresses one will be
						chosen by the system.

						If the interface does not exist or has no suitable IP
						addresses then the system will not attempt to connect
						to the server.";
					must "not(../source-address)" {
						error-message "Only one of source-interface and " +
									  "source-address may be configured";
					}
				}
			}
			leaf port {
				type uint16 {
					range 1..65535;
				}
				configd:help "TACACS+ server port";
				default "49";
			}
			leaf secret {
				type string {
					length 1..64;
					pattern "[!-~]+" {
						error-message "Secret must not contain space";
					}
				}
				configd:help "Secret for TACACS+ access [REQUIRED]";
				configd:secret "true";
				mandatory true;
			}
			leaf timeout {
				type uint32 {
					range 1..30;
				}
				configd:help "Timeout for TACACS+ session";
				default "3";
			}
			leaf hold-down-timer {
				configd:help "Prevent use of this server in case of a failure";
				description
					"If the system experiences a failure attempting to connect to,
					or communicate with, the TACACS+ server then the server will
					not be used for the configured hold down period";
				type uint32 {
					range 0..3600;
				}
				units "seconds";
				default 0;
			}
		}
	}
	augment /system:system/system-login:login {
		uses tacplus-system-login-grouping {
			refine tacplus-server/source-interface {
				must "not(/*[local-name(.) = 'routing']" +
						 "/*[local-name(.) = 'routing-instance']" +
						 "/*[local-name(.) = 'interface']" +
						 "/*[local-name(.) = 'name'][. = current()])" {
					error-message "Interface must not be configured in a routing instance";
				}
			}
		}
	}
}
